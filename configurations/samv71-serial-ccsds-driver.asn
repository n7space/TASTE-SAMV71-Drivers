SAMV71-SERIAL-CCSDS-DRIVER DEFINITIONS AUTOMATIC TAGS ::= BEGIN

Serial-CCSDS-SamV71-Device-T    ::= ENUMERATED { uart0, uart1, uart2, uart3, uart4 }

Serial-CCSDS-SamV71-Baudrate-T  ::= ENUMERATED {b9600, b19200, b38400, b57600, b115200, b230400}

Serial-CCSDS-SamV71-Parity-T    ::= ENUMERATED {even, odd}

Serial-CCSDS-SamV71-Conf-T ::= SEQUENCE {
   devname        Serial-CCSDS-SamV71-Device-T,
   speed          Serial-CCSDS-SamV71-Baudrate-T OPTIONAL,
   parity         Serial-CCSDS-SamV71-Parity-T OPTIONAL,
   bits           INTEGER (7 .. 8) OPTIONAL,
   use-paritybit  BOOLEAN  OPTIONAL
}

END
